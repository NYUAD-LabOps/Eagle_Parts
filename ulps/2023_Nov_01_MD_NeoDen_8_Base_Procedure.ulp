#usage 	"Program that outputs a NeoDen 8 proceedure for one side of a board.\n\n"
		"This ULP must include updated information on the feeders installed on the NeoDen8,\n"
		"the nozzles installed on the machine, and the ULP must be updated with lists that\n"
		"correlate the part values with the feeder list.\n"
		" \n"
        "<author>Author: Michael Davis (michael.davis@nyu.edu)</author>"


// the x,y coordinates of the first part in pnp machine coordinates
real firstPartPnpX = 260.16;
real firstPartPnpY = 177.46;
int targetSide;
 int side = 0;
 
string workDir = "f:\\GitHub\\Eagle_Parts\\ulps\\";
string boardName;
string sourcefileName;
string fileName = "C:\\GitHub\\Eagle_Parts\\ulps\\test_output_text_4.csv";

board(B){
//    workDir = filedir ( B.name );
    sourcefileName = filename ( B.name );
}


fileName = workDir + filesetext(sourcefileName, ".csv");

int Result = dlgDialog("Enter Parameters") {
  dlgHBoxLayout {
    dlgLabel("File &name:");
    dlgStringEdit(fileName);
    dlgPushButton("Bro&wse") {
      fileName = dlgDirectory("Select a directory", fileName);     
	  }
    }

  dlgHBoxLayout {
    dlgGroup("Target Side") {
      dlgRadioButton("&Top", side);
      dlgRadioButton("&Bottom", side);
      }
    }
	dlgHBoxLayout {
		dlgStretch(1);
		dlgLabel("First Part X and Y");
		dlgStretch(1);
    }
	dlgHBoxLayout {
		dlgLabel("First X:");
		dlgRealEdit(firstPartPnpX, 0.0, 650.0);
    }
	dlgHBoxLayout {
		dlgLabel("First Y:");
		dlgRealEdit(firstPartPnpY, 0.0, 650.0);
    }
	dlgSpacing(10);
	dlgHBoxLayout {
		dlgStretch(1);
		dlgPushButton("+OK")    dlgAccept();
    }
  }; 

//
//
//  Base document setup
//
//
string feeders_and_nozzles[] = {
	"#Feeder,Feeder ID,Skip,Pos X,Pos Y,Angle,Footprint,Comment,Nozzle,Pick Height,Pick Delay,Move Speed,Place Height,Place Delay,Place Speed,Accuracy,Width,Length,Thickness,Size Analyze,Tray X,Tray Y,Columns,Rows,Right Top X,Right Top Y,Vision Model,Brightness,Vision Error,Vision Flash,Feeder Type,NoisyPoint",
	"Feeder,1,NO,4.8,10.1,0,SD_CARD,SD_CARD,1,-3,0,100,0,0,100,High Speed,11.81,12.19,1.6,NO,,,,,0,0,Fly Calib,80,,7,Pneumatic,1,",
	"Feeder,2,NO,4.8,10.1,0,2_Empty,1,-3,0,100,0,0,100,High Speed,11.81,12.19,1.6,NO,,,,,0,0,Fly Calib,80,,7,Pneumatic,1,",
	"Feeder,3,NO,46.800,10.100,0,USB-B-Micro,USB-B-Micro,2,-2.5,0,100,0,0,100,High Speed,5.25,7.94,2.5,NO,,,,,0,0,Fly Calib,80,,7,Pneumatic,1,",
	"Feeder,4,NO,46.800,10.100,0,4_Empty,1,-3,0,100,0,0,100,High Speed,11.81,12.19,1.6,NO,,,,,0,0,Fly Calib,80,,7,Pneumatic,1,",
	"Feeder,5,NO,89.440,9.080,0,SMD_X_2_PADS,32.768KHz,3,-2,0,100,0,0,100,High Speed,1.5,3.2,0.69,NO,,,,,0,0,Fly Calib,80,,7,Pneumatic,1,",
	"Feeder,6,NO,110.720,9.210,0,1206,10uF_Tant,3,-2,0,100,0,0,100,High Speed,0.5,0.96,0.38,NO,,,,,0,0,Fly Calib,80,,7,Pneumatic,1,",
	"Feeder,7,NO,131.730,9.530,0,SOT323,BC846BW_NPN,4567,-2,0,100,0,0,100,High Speed,0.5,0.96,0.38,NO,,,,,0,0,Fly Calib,80,,7,Pneumatic,1,",
	"Feeder,8,NO,152.820,9.470,0,603,FB2_603,45678,-2,0,100,0,0,100,High Speed,0.5,0.96,0.38,NO,,,,,0,0,Fly Calib,80,,7,Pneumatic,1,",
	"Feeder,9,NO,173.680,9.240,0,SOT-23-5,AP2151DWG-7,3,-2,0,100,0,0,100,High Speed,2.33,2.93,0.81,NO,,,,,0,0,Fly Calib,80,,7,Pneumatic,1,",
	"Feeder,10,NO,194.920,9.530,0,1008,2.2uH,45678,-2,0,100,0,0,100,High Speed,1.35,2.03,1.3,NO,,,,,0,0,Fly Calib,80,,7,Pneumatic,1,",
	"Feeder,11,NO,215.820,9.400,0,805,Green,45678,-2,0,100,0,0,100,High Speed,1.35,2.03,1.3,NO,,,,,0,0,Fly Calib,80,,7,Pneumatic,1,",
	"Feeder,12,NO,236.690,9.280,0,402,100pF,45678,-2,0,100,0,0,100,High Speed,1.35,2.03,1.3,NO,,,,,,,No Action,80,,7,Pneumatic,1,",
	"Feeder,13,NO,257.620,9.450,0,402,22uF,45678,-2,0,100,0,0,100,High Speed,1.35,2.03,1.3,NO,,,,,,,No Action,80,,7,Pneumatic,1,",
	"Feeder,14,NO,278.530,9.320,0,402,2.2uF,45678,-2,0,100,0,0,100,High Speed,1.35,2.03,1.3,NO,,,,,,,No Action,80,,7,Pneumatic,1,",
	"Feeder,15,NO,299.860,9.360,0,402,1uF,45678,-2,0,100,0,0,100,High Speed,0.5,0.96,0.38,NO,,,,,0,0,Fly Calib,80,,7,Pneumatic,1,",
	"Feeder,16,NO,320.540,9.560,0,402,10uF,45678,-2,0,100,0,0,100,High Speed,0.67,1.14,0.38,NO,,,,,0,0,Fly Calib,80,,7,Pneumatic,1,",
	"Feeder,17,NO,342.140,9.490,0,402,0.1uF,45678,-2,0,100,0,0,100,High Speed,0.49,0.97,0.4,NO,,,,,0,0,Fly Calib,80,,7,Pneumatic,1,",
	"Feeder,18,NO,446.640,9.360,0,402,10K0,45678,-3,0,100,0,0,100,High Speed,0.53,1,0.38,NO,,,,,0,0,Fly Calib,80,,7,Pneumatic,1,",
	"Feeder,19,NO,467.550,9.430,0,402,1K0,45678,-3,0,100,0,0,100,High Speed,0.53,1,0.38,NO,,,,,0,0,Fly Calib,80,,7,Pneumatic,1,",
	"Feeder,20,NO,488.660,9.320,0,402,470R0,45678,-3,0,100,0,0,100,High Speed,0.55,1.04,0,NO,,,,,0,0,Fly Calib,80,,7,Pneumatic,1,",
	"Feeder,21,NO,509.620,9.480,0,402,33R0,45678,-3,0,100,0,0,100,High Speed,0.55,1.04,0,NO,,,,,0,0,Fly Calib,80,,7,Pneumatic,1,",
	"Feeder,22,NO,530.640,9.480,0,402,27R0,45678,-3,0,100,0,0,100,High Speed,0.52,0.99,0.38,NO,,,,,0,0,Fly Calib,80,,7,Pneumatic,1,",
	"Feeder,23,NO,551.660,9.500,0,402,15K0,45678,-3,0,100,0,0,100,High Speed,0.54,1.01,0.38,NO,,,,,0,0,Fly Calib,80,,7,Pneumatic,1,",
	"Feeder,24,NO,572.320,9.620,0,402,30K0,45678,-3,0,100,0,0,100,High Speed,0.52,0.99,0.38,NO,,,,,0,0,Fly Calib,80,,7,Pneumatic,1,",
	"Feeder,25,NO,593.260,9.810,0,402,12pF,45678,-2,0,100,0,0,100,High Speed,0.5,0.97,0.38,NO,,,,,0,0,Fly Calib,80,,7,Pneumatic,1,",
	"Feeder,26,NO,614.280,9.760,0,SMD-3225,24MHz,2,-2,0,100,0,0,100,High Speed,0.54,0.99,0.38,NO,,,,,0,0,Fly Calib,80,,7,Pneumatic,1,",
	"Feeder,27,NO,635.280,9.940,0,SMD-3225, 25MHz,2,-2,0,100,0,0,100,High Speed,0.54,0.99,0.38,NO,,,,,0,0,Fly Calib,80,,7,Pneumatic,1,",
	"Feeder,28,NO,656.290,9.790,0,402,2K2,45678,-3,0,100,0,0,100,High Speed,0.54,0.99,0.38,NO,,,,,0,0,Fly Calib,80,,7,Pneumatic,1,",
	"Feeder,29,NO,677.410,9.780,0,402,1K5,45678,-3,0,100,0,0,100,High Speed,0.54,0.99,0.38,NO,,,,,0,0,Fly Calib,80,,7,Pneumatic,1,",
	"Feeder,30,NO,698.450,9.750,0,402,18pF,5678,-2,0,100,0,0,100,High Speed,0.51,1.03,0.38,NO,,,,,0,0,Fly Calib,80,,7,Pneumatic,1,",
	"Feeder,31,NO,719.370,9.720,0,402,24pF,678,-3,0,100,0,0,100,High Speed,0.54,0.99,0.38,NO,,,,,0,0,Fly Calib,80,,7,Pneumatic,1,",
	"Feeder,32,NO,740.430,9.870,0,402,6K49,78,-3,0,100,0,0,100,High Speed,0.54,0.99,0.38,NO,,,,,0,0,Fly Calib,80,,7,Pneumatic,1,",
	"Feeder,33,NO,740.450,9.820,0,402,h2,8,-3,0,100,0,0,100,High Speed,0.54,0.99,0.38,NO,,,,,0,0,Fly Calib,80,,7,Pneumatic,1,",
	"Feeder,34,NO,1.150,518.150,0,QFN-24-M,KSZ8081_QFN_24,1,-3,0,100,0,0,100,High Speed,0.54,0.99,0.38,NO,,,,,0,0,Fly Calib,80,,7,Pneumatic,1,",
	"Feeder,67,NO,0.970,325.030,0,LQFP176_24X24,6K49,1,-4.5,20,100,0,0,100,High Speed,27,27,1.75,NO,1,1,5,4,122.920,419.850,Fly Calib,80,,7,Pneumatic,1,",
	",,,,,,,,,,,,,,,,,,,,,,,,,,,,,,,",
	"#PCB,Columns,Rows,Left Bottom X,Left Bottom Y,Left Top X,Left Top Y,Right Top X,Right Top Y,Mirror Board Left Bottom X,Mirror Board Left Bottom Y,Panelize Board Angle,Mirror Board,Marked Panel X,Marked Panel Y,Marked Panel Value,Manual Program,Feed PCB,Panelized Mark Point,PCB Width,PCB Length,Manual Mark,Test,Detect X,Detect Y,Long PCB Input,,,,,,",
	"PCB,4,1,358.080,147.140,295.970,206.990,538.090,147.520,0.000,0.000,0.120952,1,0.000,0.000,,YES,1,YES,119,240,NO,,400.000,150.000,,",
	",,,,,,,,,,,,,,,,,,,,,,,,,,,,,,,",
	"#Panel,Pos X,Pos Y,Offset X,Offset Y,Angle,Skip,Position,,,,,,,,,,,,,,,,,,,,,,,,",
	"Panel,358.08,147.141,0,0,0,NO,Align,",
	"Panel,418.080,147.270,0,0,0,NO,Align,",
	"Panel,478.086,147.391,0,0,0,NO,Align,",
	"Panel,538.089,147.523,0,0,0,NO,Align,",
	",,,,,,,,,,,,,,,,,,,,,,,,,,,,,,,",
	"#Nozzle,NozzleID,Nozzle Type,Disabled,,,,,,,,,,,,,,,,,,,,,,,,,,,,",
	"Nozzle,1,YX03,NO,,,,,,,,,,,,,,,,,,,,,,,,,,,,",
	"Nozzle,2,CN140,NO,,,,,,,,,,,,,,,,,,,,,,,,,,,,",
	"Nozzle,3,CN100,NO,,,,,,,,,,,,,,,,,,,,,,,,,,,,",
	"Nozzle,4,CN065,NO,,,,,,,,,,,,,,,,,,,,,,,,,,,,",
	"Nozzle,5,CN040,NO,,,,,,,,,,,,,,,,,,,,,,,,,,,,",
	"Nozzle,6,CN040,NO,,,,,,,,,,,,,,,,,,,,,,,,,,,,",
	"Nozzle,7,CN040,NO,,,,,,,,,,,,,,,,,,,,,,,,,,,,",
	"Nozzle,8,CN040,NO,,,,,,,,,,,,,,,,,,,,,,,,,,,,",
	",,,,,,,,,,,,,,,,,,,,,,,,,,,,,,,",
	"#Mark,Pos X,Pos Y,Min Size,Max Size,Flash,Brightness,Searching Area,Circular Similarity,Nested Mode,Select Camera,Position,,,,,,,,,,,,,,,,,,,,",
	"Mark,340.86,206.430,1.6,1.9,Middle,60,4,90,White Point,Left Camera,Align,",
	"Mark,536.243,206.871,1.6,1.9,Middle,60,4,90,White Point,Left Camera,Align,",
	",,,,,,,,,,,,,,,,,,,,,,,,,,,,,,,",
	"#Comp,Feeder ID,Comment,Footprint,Designatior,NozzleNumber,Pos X,Pos Y,Angle,Skip,Position,,,,,,,,,,,,,,,,,,,,,"
};


string foot_print[] = { "0402", "0603", "0805"," 1206", "C1210", "SOT223", "SOT323","USB_A_SMT","SD_CARD","1008","FIDUCIAL","SOT-23-5","QFN-24-M","LQFP176_24X24","SMD_3225","SMD_X_2_PADS","USB-B-Micro"};
string PartNumbers[] = {"1","2"};
string nozzles[] = { "CN400", "CN200", "CN100", "CN065", "CN040"};
string nozzle_combos[] = { "1", "2", "3", "4", "5"};
int PARTCOUNT = 67;

string feeder_desc[] = {
"SD_CARD",
"2_Empty",
"USB-B-Micro",
"4_Empty",
"32.768KHz",
"10uF_Tant",
"BC846BW_NPN",
"FB2_603",
"AP2151DWG-7",
"2.2uH",
"Green",
"100pF",
"22uF",
"2.2uF",
"1uF",
"10uF",
"0.1uF",
"10K0",
"1K0",
"470R0",
"33R0",
"27R0",
"15K0",
"30K0",
"12pF",
"24MHz",
"25MHz",
"2K2",
"1K5",
"18pF",
"24pF",
"6K49",
"F33",
"KSZ8081_QFN_24",
"S7G2LQFP176"
};

int feeder_id[] = {1,2,3,4,5,6,7,8,9,10,11,12,13,14,15,16,17,18,19,20,21,22,23,24,25,26,27,28,29,30,31,32,33,34,67};
string nozzle_id[] = {
"1",
"1",
"2",
"2",
"3",
"3",
"4",
"4",
"3",
"4",
"4",
"4",
"4",
"4",
"4",
"4",
"4",
"4",
"4",
"4",
"4",
"4",
"4",
"4",
"4",
"2",
"2",
"4",
"4",
"5",
"6",
"7",
"8",
"1",
"1"
};


real firstPartBoardX,firstPartBoardY;  // the x,y coordinates of the first part in board coordinates
real deltaX, deltaY;  //  The distance of the part from the first part.

output(fileName, "wt") {
int i, feeder_index,wasSmd;
	if(side==0){
		targetSide = LAYER_TOP;
	}else{
		targetSide = LAYER_BOTTOM;
	}
	for(i=0;feeders_and_nozzles[i];i++) {
		printf("%s\n",feeders_and_nozzles[i]);
	}
	int partIndex = 0;
	board(B){
		string board_layer = "none";
		int board_side;
		real Eangle,Eangle1;
		
		B.elements(E){
			wasSmd = 0;
			E.package.contacts ( C ) {
				if ( C.smd ) {
					if ( C.smd.layer == targetSide ) {
						wasSmd = 1;
					}
				}
			}
			if(wasSmd){
				feeder_index = 1000;
				for(i=0;feeder_desc[i];i++) {
					if(feeder_desc[i]==E.value) feeder_index = i;
				}
				if(E.value=="FIDUCIAL" || E.value=="USB-A"){
				}else{
					if(partIndex==0){
						firstPartBoardX = u2mm(E.x);
						firstPartBoardY = u2mm(E.y);
						partIndex++;
					}
					deltaX = u2mm(E.x) - firstPartBoardX;
					deltaY = u2mm(E.y) - firstPartBoardY;
					Eangle = E.angle;
					if(Eangle>=180){
						Eangle1 = Eangle - 180;
						Eangle = Eangle1;
					}
					printf("Comp,%u, %s, %s,%s,%s, %f, %f, %f,,,,,,,,,,,,,,,,,,,,,,,\n",feeder_id[feeder_index],E.value,E.footprint.name,E.name,nozzle_id[feeder_index], firstPartPnpX + deltaX, firstPartPnpY + deltaY, Eangle);
				}
			}
        }
	}
}
